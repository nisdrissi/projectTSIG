FME workspace postgis2shape_testLambert93.fmw
Shutdown Python:
      #import distutils.dir_util
      #import shutil
      #import os
      #import time
      #import locale

      #fm_log = open('$(FME_MF_DIR_ENCODED)2_tests_fme_donnees_sortie\loggs.log', 'a')
      #fme_log.write(time.strftime('%m/%d/%Y %I:%M:%S', time.localtime()) + ',' + shl_count + ',' + bhl_count + ',' + '\n')

Parameters:
- DestDataset_SHAPE = $(FME_MF_DIR)2_tests_fme_donnees_sortie   # Destination Esri Shape Folder
- SourceDataset_POSTGIS = postgres@localhost:5433/test_import01   # source
- FEATURE_TYPES = routes.troncon_voie_ferree routes.troncon_route routes.troncon_chemin routes.surface_route routes.aire_triage
- SourceDataset_SHAPE = $(FME_MF_DIR)1_tests_fme_donnees_entree\communes-20150101-50m.shp   # Source Esri Shape File(s)
- SRS = EPSG:2154   # Système de Référence Spatiale

Readers:
- POSTGIS_1: POSTGIS from $(SourceDataset_POSTGIS)
- SHAPE_2: SHAPE from $(SourceDataset_SHAPE)

Writers:
- SHAPE_1: SHAPE to $(DestDataset_SHAPE)

communes-20150101-50m (reader SHAPE_2)
    attributes: insee char(80), nom char(80), wikipedia char(80), surf_m2 number(24,15)
routes.troncon_voie_ferree (reader POSTGIS_1)
    attributes: source_géométrique varchar(27), nature varchar(27), electrifié varchar(3), franchissement varchar(10), largeur_voie varchar(10), nombre_voies int4, position_sol int4, z_ini numeric(9,1), z_fin numeric(9,1), numéro varchar(10), département_gestionnaire varchar(3), classement varchar(16), largeur_chaussée numeric(10,2), nom varchar(80), fictif bool, z_moyen numeric(9,1)
    -> Reprojector_2
Note: projection Lambert93 à partir de n'importe quel SRS
Reprojector_2
    RASTER_CELL_SIZE = Preserve Cells
    INTERPOLATION_TYPE_NAME = Nearest Neighbor
    SOURCE = Read from feature
    DEST = $(SRS)
    REPROJECTED -> File100 (writer SHAPE_1)
File100 (writer SHAPE_1)
    attributes: source_géo char(27), nature char(27), electrifié char(3), franchisse char(10), largeur_vo char(10), nombre_voi number(11,0), position_s number(11,0), z_ini number(9,1), z_fin number(9,1), numéro char(10), départemen char(3), classement char(16), largeur_ch number(10,2), nom char(80), fictif logical, z_moyen number(9,1)
